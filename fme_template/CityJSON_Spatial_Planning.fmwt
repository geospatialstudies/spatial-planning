FME workspace CityJSON_Spatial_Planning.fmwt
Title: CityJSON Spatial Planning Extension

Parameters:
- DestDataset_CITYJSON_3 = E:\OneDrive - itu.edu.tr\Belgeler\Makale\2021_Babs_Special_Issue\sample_output_citygml\zonings\zp4.json   # Destination CityJSON File
- SourceDataset_GEOJSON_4 = E:\OneDrive - itu.edu.tr\Belgeler\Makale\2021_Babs_Special_Issue\sample_zoning_plans\zoning_plans\4\zp4_plangroup1.geojson   # Source GeoJSON File or URL
- SourceDataset_GEOJSON_5 = E:\OneDrive - itu.edu.tr\Belgeler\Makale\2021_Babs_Special_Issue\sample_zoning_plans\zoning_plans\4\zp4_planunit3.geojson   # Source GeoJSON File or URL
- SourceDataset_GEOJSON = E:\OneDrive - itu.edu.tr\Belgeler\Makale\2021_Babs_Special_Issue\sample_zoning_plans\zoning_plans\4\zp4_planblock3.geojson   # Source GeoJSON File or URL

Readers:
- GEOJSON_3: GEOJSON from $(SourceDataset_GEOJSON_4)
- GEOJSON_2: GEOJSON from $(SourceDataset_GEOJSON_5)
- GEOJSON_1: GEOJSON from $(SourceDataset_GEOJSON)

Writers:
- CITYJSON_2: CITYJSON to $(DestDataset_CITYJSON_3) in TURK-TM30

Bookmark: Spatial Planning Extension
Note: PlanUnit
zp4_planunit3 (reader GEOJSON_2)
    attributes: zoningType string, zoningSubType string, easement string, layer string, path string, area float, permitType string, puID string, zoningName string, planID int, maxHeight int, volume float, planType string, pbID string, parents string
    -> AttributeCopier
AttributeCopier
    ATTR_TABLE:
      COPY parents > cityjson_parents{0}
      COPY puID > fid
    MISSING_INPUT_ATTRS = REMOVE
    -> Extruder_2
Extruder_2
    DIRECTION = Vertical
    DISTANCE = @Value(maxHeight)
    EXTRUDED -> CityGMLGeometrySetter_2
CityGMLGeometrySetter_2
    GEOM = lod2Solid
    ROLE = cityObjectMember
    -> +PlanUnit (writer CITYJSON_2)
+PlanUnit (writer CITYJSON_2)
    attributes: fid string, puID string, maxHeight int32, zoningType string, zoningName string, easement string, planType string, planID int32, area real64, volume real64, pbID string, zoningSubType string, permitType string
Note: PlanGroup
zp4_plangroup1 (reader GEOJSON_3)
    attributes: pgID string, pbID string, children string, maxHeight int
    -> AttributeCopier_3
AttributeCopier_3
    ATTR_TABLE:
      COPY pgID > fid
      COPY children > cityjson_children{0}
    MISSING_INPUT_ATTRS = REMOVE
    -> Extruder_3
Extruder_3
    DIRECTION = Vertical
    DISTANCE = @Value(maxHeight)
    EXTRUDED -> CityGMLGeometrySetter_4
CityGMLGeometrySetter_4
    GEOM = lod2Solid
    ROLE = cityObjectMember
    -> +PlanGroup (writer CITYJSON_2)
+PlanGroup (writer CITYJSON_2)
    attributes: fid string, pgID string
Note: PlanBlock
zp4_planblock3 (reader GEOJSON_1)
    attributes: pgID string, pbID string, parents string, puID_2 string, children string, maxHeight int
    -> AttributeCopier_2
AttributeCopier_2
    ATTR_TABLE:
      COPY pbID > fid
      COPY parents > cityjson_parents{0}
      COPY children > cityjson_children{0}
    MISSING_INPUT_ATTRS = REMOVE
    -> Extruder_4
Extruder_4
    DIRECTION = Vertical
    DISTANCE = @Value(maxHeight)
    EXTRUDED -> CityGMLGeometrySetter_3
CityGMLGeometrySetter_3
    GEOM = lod2Solid
    ROLE = cityObjectMember
    -> +PlanBlock (writer CITYJSON_2)
+PlanBlock (writer CITYJSON_2)
    attributes: fid string, pbID string, pgID string, blockName string
